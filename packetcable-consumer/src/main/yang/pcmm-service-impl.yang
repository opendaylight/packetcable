module pcmm-service-impl {

    yang-version 1;
    namespace "urn:opendaylight:params:xml:ns:yang:controller:config:pcmm-service:impl";
    prefix "pcmm-service-impl";

    import config { prefix config; revision-date 2013-04-05; }
    import rpc-context { prefix rpcx; revision-date 2013-06-17; }    
    import opendaylight-md-sal-binding { prefix mdsal; revision-date 2013-10-28; }

    description
        "This module contains the base YANG definitions for
        pcmm-service impl implementation.";

    revision "2014-08-10" {
        description
            "Initial revision.";
    }

    // This is the definition of pcmm service interface identity.
    identity pcmm-service {
        base "config:service-type";
        config:java-class "org.opendaylight.controller.org.pcmm.api.PcmmService";
    }

    // This is the definition of pcmm service implementation module identity. 
    identity pcmm-service-impl {
            base config:module-type;
            config:provided-service pcmm-service;
            config:java-name-prefix PcmmService;
    }

    augment "/config:modules/config:module/config:configuration" {
        case pcmm-service-impl {
            when "/config:modules/config:module/config:type = 'pcmm-service-impl'";

            container rpc-registry {
                uses config:service-ref {
                    refine type {
                        mandatory true;
                        config:required-identity mdsal:binding-rpc-registry;
                    }
                }
            }

            container notification-service {
                uses config:service-ref {
                    refine type {
                        mandatory true;
                        config:required-identity mdsal:binding-notification-service;
                    }
                }
            }
        }
    }
    
    augment "/config:modules/config:module/config:state" {
        case pcmm-service-impl {
            when "/config:modules/config:module/config:type = 'pcmm-service-impl'";
            
            rpcx:rpc-context-instance "send-gate-set-rpc";
            rpcx:rpc-context-instance "send-gate-delete-rpc";
            rpcx:rpc-context-instance "send-gate-info-rpc";
            rpcx:rpc-context-instance "send-gate-synchronize-rpc";
              
        }
    }

    identity send-gate-set-rpc;

    rpc send-gate-set {
        description
          "Shortcut JMX call to send a gate-set message for testing.";
          
        input {
            uses rpcx:rpc-context-ref {
                refine context-instance {
                    rpcx:rpc-context-instance send-gate-set-rpc;
                }
            }
        }
        
        output {
            leaf result {
                type boolean;
            }
        }
    }
    
      identity send-gate-delete-rpc;

    rpc send-gate-delete {
        description
          "Shortcut JMX call to send a gate-delete message for testing.";
          
        input {
            uses rpcx:rpc-context-ref {
                refine context-instance {
                    rpcx:rpc-context-instance send-gate-delete-rpc;
                }
            }
        }
        
        output {
            leaf result {
                type boolean;
            }
        }
    }
    
     identity send-gate-synchronize-rpc;

    rpc send-gate-synchronize {
        description
          "Shortcut JMX call to send a gate-Synchronize message for testing.";
          
        input {
            uses rpcx:rpc-context-ref {
                refine context-instance {
                    rpcx:rpc-context-instance send-gate-synchronize-rpc;
                }
            }
        }
        
        output {
            leaf result {
                type boolean;
            }
        }
    }
    
          identity send-gate-info-rpc;

    rpc send-gate-info {
        description
          "Shortcut JMX call to send a gate-info message for testing.";
          
        input {
            uses rpcx:rpc-context-ref {
                refine context-instance {
                    rpcx:rpc-context-instance send-gate-info-rpc;
                }
            }
        }
        
        output {
            leaf result {
                type boolean;
            }
        }
    }
}

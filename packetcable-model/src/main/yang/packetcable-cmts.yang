module packetcable-cmts
{
    namespace "urn:opendaylight:node:cmts";
    prefix "cmts";

    import ietf-yang-types 	{ prefix yang; }
    import ietf-inet-types 	{ prefix inet; }
    import opendaylight-inventory {prefix inv;revision-date "2013-08-19";}
    import yang-ext {prefix ext; revision-date "2013-07-09";}
//    import ietf-interfaces 	{ prefix if;   }
//    import ietf-snmp    	{ prefix snmp; }
//    import ietf-reverse-ssh    	{ prefix rssh; }

    description "This module contains a collection of CMTS definitions";
    organization "OpenDaylight Project";

    revision 2014-09-09 {
        description "Initial revision of packetcable cmts";
    }        

    grouping cmts-node-attributes {
        description "A PCMM capable CMTS and other available configuration resources.";
        
        leaf address {
            type inet:ip-address;
            description "IP Address of CMTS";
        }
        
        leaf port {
            type inet:port-number;
            description "TCP port number to connect";
            default 3918;
        }
    }
    
    augment "/inv:nodes/inv:node" {
        ext:augment-identifier "cmts-capable-node";
        container cmts-node {
            uses cmts-node-attributes ;
        }
    }
}

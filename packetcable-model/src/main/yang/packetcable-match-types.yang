module packetcable-match-types
{
    namespace "urn:opendaylight:packetcable:match:types";
    prefix "packet-cable-match";

    import yang-ext {prefix ext; revision-date "2013-07-09";}
    import flow-node-inventory {prefix fni; revision-date "2013-08-19"; }
    import opendaylight-inventory {prefix inv;revision-date "2013-08-19";}
    import sal-flow {prefix sal-flow;revision-date "2013-08-19";}
    import packet-processing {prefix sal-packet;revision-date "2013-07-09";}
    import ietf-inet-types {prefix inet; revision-date "2010-09-24";}
    import ietf-yang-types {prefix yang; revision-date "2010-09-24";}
    import opendaylight-flow-types {prefix flow;revision-date "2013-10-26";}
    import opendaylight-flow-statistics {prefix odl-flow-stats;revision-date "2013-08-19";}

    revision 2014-09-09 {
        description "Initial revision of packetcable match types";
    }        
    

    grouping "udp-match-ranges-attributes" {
        container upd-match-ranges {
            leaf udp-source-port-start {
                description "UDP source port start.";
                type inet:port-number;
            }
            leaf udp-source-port-end {
                description "UDP source port end.";
                type inet:port-number;
            }
            leaf udp-destination-port-start {
                description "UDP destination port start.";
                type inet:port-number;
            }
            leaf udp-destination-port-end {
                description "UDP destination port end.";
                type inet:port-number;
            }
        }
    }

    
    //  MATCH augmentations for udp-match-range
    // RPCS
    augment "/sal-flow:add-flow/sal-flow:input/sal-flow:match" {
        ext:augment-identifier "udp-match-ranges-rpc-add-flow";
        uses udp-match-ranges-attributes;
    }
    augment "/sal-flow:remove-flow/sal-flow:input/sal-flow:match" {
        ext:augment-identifier "udp-match-ranges-rpc-remove-flow";
        uses udp-match-ranges-attributes;
    }
    augment "/sal-flow:update-flow/sal-flow:input/sal-flow:original-flow/sal-flow:match" {
        ext:augment-identifier "udp-match-ranges-rpc-update-flow-original";
        uses udp-match-ranges-attributes;
    }
    augment "/sal-flow:update-flow/sal-flow:input/sal-flow:updated-flow/sal-flow:match" {
        ext:augment-identifier "udp-match-ranges-rpc-update-flow-updated";
        uses udp-match-ranges-attributes;
    }

    // DATA
    augment "/inv:nodes/inv:node/fni:table/fni:flow/fni:match" {
        ext:augment-identifier "udp-match-ranges-nodes-node-table-flow";
        uses udp-match-ranges-attributes;
    }

    // NOTIFICATIONS
    augment "/sal-flow:switch-flow-removed/sal-flow:match" {
        ext:augment-identifier "udp-match-ranges-notif-switch-flow-removed";
        uses udp-match-ranges-attributes;
    }
    augment "/sal-packet:packet-received/sal-packet:match" {
        ext:augment-identifier "udp-match-ranges-notif-packet-in";
        uses udp-match-ranges-attributes;
    }
    augment "/odl-flow-stats:flows-statistics-update/odl-flow-stats:flow-and-statistics-map-list/odl-flow-stats:match" {
        ext:augment-identifier "udp-match-ranges-notif-update-flow-stats";
        uses udp-match-ranges-attributes;
    }
    
    grouping "tcp-match-ranges-attributes" {
        container tcp-match-ranges {
            leaf tcp-source-port-start {
                description "TCP source port start.";
                type inet:port-number;
            }
            leaf tcp-source-port-end {
                description "TCP source port end.";
                type inet:port-number;
            }
            leaf tcp-destination-port-start {
                description "TCP destination port start.";
                type inet:port-number;
            }
            leaf tcp-destination-port-end {
                description "TCP destination port end.";
                type inet:port-number;
            }
        }
    }
    
//  MATCH augmentations for tcp-match-range
// RPCS
    augment "/sal-flow:add-flow/sal-flow:input/sal-flow:match" {
        ext:augment-identifier "tcp-match-ranges-rpc-add-flow";
        uses tcp-match-ranges-attributes;
    }
    augment "/sal-flow:remove-flow/sal-flow:input/sal-flow:match" {
        ext:augment-identifier "tcp-match-ranges-rpc-remove-flow";
        uses tcp-match-ranges-attributes;
    }
    augment "/sal-flow:update-flow/sal-flow:input/sal-flow:original-flow/sal-flow:match" {
        ext:augment-identifier "tcp-match-ranges-rpc-update-flow-original";
        uses tcp-match-ranges-attributes;
    }
    augment "/sal-flow:update-flow/sal-flow:input/sal-flow:updated-flow/sal-flow:match" {
        ext:augment-identifier "tcp-match-ranges-rpc-update-flow-updated";
        uses tcp-match-ranges-attributes;
    }

// DATA
    augment "/inv:nodes/inv:node/fni:table/fni:flow/fni:match" {
        ext:augment-identifier "tcp-match-ranges-nodes-node-table-flow";
        uses tcp-match-ranges-attributes;
    }

// NOTIFICATIONS
    augment "/sal-flow:switch-flow-removed/sal-flow:match" {
        ext:augment-identifier "tcp-match-ranges-notif-switch-flow-removed";
        uses tcp-match-ranges-attributes;
    }
    augment "/sal-packet:packet-received/sal-packet:match" {
        ext:augment-identifier "tcp-match-ranges-notif-packet-in";
        uses tcp-match-ranges-attributes;
    }
    augment "/odl-flow-stats:flows-statistics-update/odl-flow-stats:flow-and-statistics-map-list/odl-flow-stats:match" {
        ext:augment-identifier "tcp-match-ranges-notif-update-flow-stats";
        uses tcp-match-ranges-attributes;
    }

    grouping subscriber-id {
        leaf subscriber-id {
            type inet:ip-address;
            description "Subscriber Id";
        }
    }
    
//  MATCH augmentations for susbcriber-id
// RPCS
    augment "/sal-flow:add-flow/sal-flow:input/sal-flow:match" {
        ext:augment-identifier "subscriber-id-rpc-add-flow";
        uses subscriber-id;
    }
    augment "/sal-flow:remove-flow/sal-flow:input/sal-flow:match" {
        ext:augment-identifier "subscriber-id-rpc-remove-flow";
        uses subscriber-id;
    }
    augment "/sal-flow:update-flow/sal-flow:input/sal-flow:original-flow/sal-flow:match" {
        ext:augment-identifier "subscriber-id-rpc-update-flow-original";
        uses subscriber-id;
    }
    augment "/sal-flow:update-flow/sal-flow:input/sal-flow:updated-flow/sal-flow:match" {
        ext:augment-identifier "subscriber-id-rpc-update-flow-updated";
        uses subscriber-id;
    }

// DATA
    augment "/inv:nodes/inv:node/fni:table/fni:flow/fni:match" {
        ext:augment-identifier "subscriber-id-nodes-node-table-flow";
        uses subscriber-id;
    }

// NOTIFICATIONS
    augment "/sal-flow:switch-flow-removed/sal-flow:match" {
        ext:augment-identifier "subscriber-id-notif-switch-flow-removed";
        uses subscriber-id;
    }
    augment "/sal-packet:packet-received/sal-packet:match" {
        ext:augment-identifier "subscriber-id-notif-packet-in";
        uses subscriber-id;
    }
    augment "/odl-flow-stats:flows-statistics-update/odl-flow-stats:flow-and-statistics-map-list/odl-flow-stats:match" {
        ext:augment-identifier "subscriber-id-notif-update-flow-stats";
        uses subscriber-id;
    }
    
}

module packetcable-policy-server-impl {

    yang-version 1;
    namespace "urn:opendaylight:params:xml:ns:yang:packetcable:packetcable-policy-server:impl";
    prefix "packetcable-policy-server-impl";

    import config { prefix config; revision-date 2013-04-05; }
    import rpc-context { prefix rpcx; revision-date 2013-06-17; }
    import opendaylight-md-sal-binding { prefix mdsal; revision-date 2013-10-28; }
    import ietf-inet-types {prefix inet;revision-date 2013-07-15;}

    description
        "This module contains the base YANG definitions for
        packetcable-policy-server impl implementation.";

    revision "2014-01-31" {
        description
            "Initial revision.";
    }

    // This is the definition of the service implementation as a module identity.
    identity packetcable-policy-server-impl {
            base config:module-type;
            config:java-name-prefix PacketcableProvider;
    }

    // Augments the 'configuration' choice node under modules/module.
    augment "/config:modules/config:module/config:configuration" {
        case packetcable-policy-server-impl {
            when "/config:modules/config:module/config:type = 'packetcable-policy-server-impl'";

		      //wires in the data-broker and rpc services
		      container data-broker {
		        uses config:service-ref {
		          refine type {
		              mandatory true;
		              config:required-identity mdsal:binding-broker-osgi-registry;
		          }
		        }
		      }
		      container rpc-registry {
		        uses config:service-ref {
		          refine type {
		             mandatory true;
		             config:required-identity mdsal:binding-rpc-registry;
		          }
		        }
		      }
        }
    }
}

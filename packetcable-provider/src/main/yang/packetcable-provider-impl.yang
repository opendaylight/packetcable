module packetcable-provider-impl {

    yang-version 1;
    namespace "urn:opendaylight:params:xml:ns:yang:packetcable:packetcable-provider:impl";
    prefix "packetcable-provider-impl";

    import config { prefix config; revision-date 2013-04-05; }
    import rpc-context { prefix rpcx; revision-date 2013-06-17; }
    import opendaylight-md-sal-binding { prefix mdsal; revision-date 2013-10-28; }
    import packetcable-provider { prefix pcp; revision-date 2014-01-31; }
    import ietf-inet-types {prefix inet;revision-date 2010-09-24;}

    description
        "This module contains the base YANG definitions for
        packetcable-provider impl implementation.";

    revision "2014-01-31" {
        description
            "Initial revision.";
    }

    // This is the definition of the service implementation as a module identity.
    identity packetcable-provider-impl {
            base config:module-type;
            config:provided-service pcp:packetcable-provider;
            // Specifies the prefix for generated java classes.
            config:java-name-prefix PacketcableProvider;
    }

    // Augments the 'configuration' choice node under modules/module.
    augment "/config:modules/config:module/config:configuration" {
        case packetcable-provider-impl {
            when "/config:modules/config:module/config:type = 'packetcable-provider-impl'";
            container broker {
                uses config:service-ref {
                    refine type {
                        mandatory true;
                        config:required-identity mdsal:binding-broker-osgi-registry;
                    }
                }
            }
        }
    }
}
